module ietf-if-flex-e {
  yang-version 1.1;
  namespace "urn:ietf:params:xml:ns:yang:ietf-if-flex-e";
  prefix "flex-e";

  import iana-if-type {
    prefix ianaift;
  }
  
  import ietf-interfaces {
    prefix if;
    reference
      "RFC8343: A YANG Data Model for Interface Management";
  }

  organization "IETF CCAMP Working Group";
  contact
    "WG Web:   http://tools.ietf.org/wg/ccamp/
     WG List:  <mailto:ccamp@ietf.org>";
  
  description
    "A YANG data model for managing Flexible Ethernet interfaces.
     Reference: OIF Flex 2.0

     Currently only intended to agree overall shape/structure of the
     YANG model";

  revision "2019-11-25" {
    description "Initial version, some what derived from
                 draft-jiang-ccamp-flexe-yang-02";
    reference
      "tbd";
  }

  augment "/if:interfaces/if:interface" {
    
    when "if:type = 'ianaift:flexEthGroup'" {
      description "Applies to bonded Ethernet interfaces";
    }
    
    description
      "Augment interface model with OIF Flex Ethernet interface
       specific configuration nodes. Each flexEthernet interface
       represents a FlexE Group configured in a device.";

    container flex-e {
      description
        "The struct containing all FlexE related configuration
         (see OIF FlexE 2.0 Section 6.1).
         Note that max number of FlexE groups in a network is 63.";

      leaf group-number {
        mandatory true;
        type uint32 {
          range "1..1048574";
        }
        description
          "The FlexE group number";
        reference
          "FlexE Group Number as defined in Section 7.3.6 of FlexE
           2.0.";
      }

      leaf more-group-config-here {
        type string;
      }

      list bonded-phy {
        key "name";
        unique "phy-number";
        description
          "List of PHY interfaces bonded in the FlexE group.";

        leaf name {
          type if:interface-ref;
          description
            "The name of the underlying Physical Ethernet interface
             bonded into this Flex-E group.";
        }

        leaf phy-number {
          type uint8 {
            range "1 .. 254";
          }
          description
            "PHY number of a FlexE PHY.

             The maximum PHY number depends on the type of PHYs
             bonded into the Flex-E group:
                100GBASE-R, max is 254,
                200GBASE-R, max is 126,
                400GBASE-R, max is 62.";
        }

        leaf more-bonded-phy-config-here {
          type string;
        }
      }

      list client-interface {            
        key "name";
        unique "id";
        description
          "List of FlexE clients in a FlexE Group.";

        leaf name {
          type if:interface-ref {
            require-instance false;
          }
          description
            "A client interface of the flex-e group.  The 'type' of
             the client interface must be (or derived from)
             'ianaift:ethernetCsmacd'.";
        }

        leaf id {
          type uint16 {
            range "1..65534";
          }
          description
            "";
          reference
            "FlexE Client field as defined in FlexE 2.0 Section
               7.3.4.";
        }

        leaf more-flex-e-client-config-here {
          type string;
        }
      }
    }
  }
}
